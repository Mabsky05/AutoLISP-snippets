;print in layout space using default settings
;TODO complete print after save dialog

(command "-plot"
"y"
"Layout1"
"DWG to PDF"
"ISO A4 (210.00 x 297.00 MM)"
"Millimeters"
"Landscape"
"No"
"Layout"
"1:1"
"0.00, 0.00"
"Yes"
"acad.ctb"
"Yes"
"No"
"Yes"
"No"
;Save dialog appears
)
